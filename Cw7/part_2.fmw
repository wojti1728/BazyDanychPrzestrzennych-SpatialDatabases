FME workspace part_2.fmw

Parameters:
- SourceDataset_SHAPEFILE = D:\AGH-studia\Semestr_7\Bazy_Danych_Przestrzennych\Laby\cw7\bdline_essh_gb\Data\GB\scotland_and_wales_region.shp   # Source Esri Shapefile(s)
- SourceDataset_GEOTIFF = ""D:\AGH-studia\Semestr_7\Bazy_Danych_Przestrzennych\Laby\cw7\ras250_gb\ras250_gb\data\HP.tif" "D:\AGH-studia\Semestr_7\Bazy_Danych_Przestrzennych\Laby\cw7\ras250_gb\ras250_gb\data\HT.tif" "D:\AGH-studia\Semestr_7\Bazy_Danych_Przestrzennych\Laby\cw7\ras250_gb\ras250_gb\data\HU.tif" "D:\AGH-studia\Semestr_7\Bazy_Danych_Przestrzennych\Laby\cw7\ras250_gb\ras250_gb\data\HW.tif" "D:\AGH-studia\Semestr_7\Bazy_Danych_Przestrzennych\Laby\cw7\ras250_gb\ras250_gb\data\HX.tif" "D:\AGH-studia\Semestr_7\Bazy_Danych_Przestrzennych\Laby\cw7\ras250_gb\ras250_gb\data\HY.tif" "D:\AGH-studia\Semestr_7\Bazy_Danych_Przestrzennych\Laby\cw7\ras250_gb\ras250_gb\data\HZ.tif" "D:\AGH-studia\Semestr_7\Bazy_Danych_Przestrzennych\Laby\cw7\ras250_gb\ras250_gb\data\NA.tif" "D:\AGH-studia\Semestr_7\Bazy_Danych_Przestrzennych\Laby\cw7\ras250_gb\ras250_gb\data\NB.tif" "D:\AGH-studia\Semestr_7\Bazy_Danych_Przestrzennych\Laby\cw7\ras250_gb\ras250_gb\data\NC.tif" "D:\AGH-studia\Semestr_7\Bazy_Danych_Przestrzennych\Laby\cw7\ras250_gb\ras250_gb\data\ND.tif" "D:\AGH-studia\Semestr_7\Bazy_Danych_Przestrzennych\Laby\cw7\ras250_gb\ras250_gb\data\NF.tif" "D:\AGH-studia\Semestr_7\Bazy_Danych_Przestrzennych\Laby\cw7\ras250_gb\ras250_gb\data\NG.tif" "D:\AGH-studia\Semestr_7\Bazy_Danych_Przestrzennych\Laby\cw7\ras250_gb\ras250_gb\data\NH.tif" "D:\AGH-studia\Semestr_7\Bazy_Danych_Przestrzennych\Laby\cw7\ras250_gb\ras250_gb\data\NJ.tif" "D:\AGH-studia\Semestr_7\Bazy_Danych_Przestrzennych\Laby\cw7\ras250_gb\ras250_gb\data\NK.tif" "D:\AGH-studia\Semestr_7\Bazy_Danych_Przestrzennych\Laby\cw7\ras250_gb\ras250_gb\data\NL.tif" "D:\AGH-studia\Semestr_7\Bazy_Danych_Przestrzennych\Laby\cw7\ras250_gb\ras250_gb\data\NM.tif" "D:\AGH-studia\Semestr_7\Bazy_Danych_Przestrzennych\Laby\cw7\ras250_gb\ras250_gb\data\NN.tif" "D:\AGH-studia\Semestr_7\Bazy_Danych_Przestrzennych\Laby\cw7\ras250_gb\ras250_gb\data\NO.tif" "D:\AGH-studia\Semestr_7\Bazy_Danych_Przestrzennych\Laby\cw7\ras250_gb\ras250_gb\data\NR.tif" "D:\AGH-studia\Semestr_7\Bazy_Danych_Przestrzennych\Laby\cw7\ras250_gb\ras250_gb\data\NS.tif" "D:\AGH-studia\Semestr_7\Bazy_Danych_Przestrzennych\Laby\cw7\ras250_gb\ras250_gb\data\NT.tif" "D:\AGH-studia\Semestr_7\Bazy_Danych_Przestrzennych\Laby\cw7\ras250_gb\ras250_gb\data\NU.tif" "D:\AGH-studia\Semestr_7\Bazy_Danych_Przestrzennych\Laby\cw7\ras250_gb\ras250_gb\data\NW.tif" "D:\AGH-studia\Semestr_7\Bazy_Danych_Przestrzennych\Laby\cw7\ras250_gb\ras250_gb\data\NX.tif" "D:\AGH-studia\Semestr_7\Bazy_Danych_Przestrzennych\Laby\cw7\ras250_gb\ras250_gb\data\NY.tif" "D:\AGH-studia\Semestr_7\Bazy_Danych_Przestrzennych\Laby\cw7\ras250_gb\ras250_gb\data\NZ.tif" "D:\AGH-studia\Semestr_7\Bazy_Danych_Przestrzennych\Laby\cw7\ras250_gb\ras250_gb\data\OV.tif" "D:\AGH-studia\Semestr_7\Bazy_Danych_Przestrzennych\Laby\cw7\ras250_gb\ras250_gb\data\SC.tif" "D:\AGH-studia\Semestr_7\Bazy_Danych_Przestrzennych\Laby\cw7\ras250_gb\ras250_gb\data\SD.tif" "D:\AGH-studia\Semestr_7\Bazy_Danych_Przestrzennych\Laby\cw7\ras250_gb\ras250_gb\data\SE.tif" "D:\AGH-studia\Semestr_7\Bazy_Danych_Przestrzennych\Laby\cw7\ras250_gb\ras250_gb\data\SH.tif" "D:\AGH-studia\Semestr_7\Bazy_Danych_Przestrzennych\Laby\cw7\ras250_gb\ras250_gb\data\SJ.tif" "D:\AGH-studia\Semestr_7\Bazy_Danych_Przestrzennych\Laby\cw7\ras250_gb\ras250_gb\data\SK.tif" "D:\AGH-studia\Semestr_7\Bazy_Danych_Przestrzennych\Laby\cw7\ras250_gb\ras250_gb\data\SM.tif" "D:\AGH-studia\Semestr_7\Bazy_Danych_Przestrzennych\Laby\cw7\ras250_gb\ras250_gb\data\SN.tif" "D:\AGH-studia\Semestr_7\Bazy_Danych_Przestrzennych\Laby\cw7\ras250_gb\ras250_gb\data\SO.tif" "D:\AGH-studia\Semestr_7\Bazy_Danych_Przestrzennych\Laby\cw7\ras250_gb\ras250_gb\data\SP.tif" "D:\AGH-studia\Semestr_7\Bazy_Danych_Przestrzennych\Laby\cw7\ras250_gb\ras250_gb\data\SR.tif" "D:\AGH-studia\Semestr_7\Bazy_Danych_Przestrzennych\Laby\cw7\ras250_gb\ras250_gb\data\SS.tif" "D:\AGH-studia\Semestr_7\Bazy_Danych_Przestrzennych\Laby\cw7\ras250_gb\ras250_gb\data\ST.tif" "D:\AGH-studia\Semestr_7\Bazy_Danych_Przestrzennych\Laby\cw7\ras250_gb\ras250_gb\data\SU.tif" "D:\AGH-studia\Semestr_7\Bazy_Danych_Przestrzennych\Laby\cw7\ras250_gb\ras250_gb\data\SV.tif" "D:\AGH-studia\Semestr_7\Bazy_Danych_Przestrzennych\Laby\cw7\ras250_gb\ras250_gb\data\SW.tif" "D:\AGH-studia\Semestr_7\Bazy_Danych_Przestrzennych\Laby\cw7\ras250_gb\ras250_gb\data\SX.tif" "D:\AGH-studia\Semestr_7\Bazy_Danych_Przestrzennych\Laby\cw7\ras250_gb\ras250_gb\data\SY.tif" "D:\AGH-studia\Semestr_7\Bazy_Danych_Przestrzennych\Laby\cw7\ras250_gb\ras250_gb\data\SZ.tif" "D:\AGH-studia\Semestr_7\Bazy_Danych_Przestrzennych\Laby\cw7\ras250_gb\ras250_gb\data\TA.tif" "D:\AGH-studia\Semestr_7\Bazy_Danych_Przestrzennych\Laby\cw7\ras250_gb\ras250_gb\data\TF.tif" "D:\AGH-studia\Semestr_7\Bazy_Danych_Przestrzennych\Laby\cw7\ras250_gb\ras250_gb\data\TG.tif" "D:\AGH-studia\Semestr_7\Bazy_Danych_Przestrzennych\Laby\cw7\ras250_gb\ras250_gb\data\TL.tif" "D:\AGH-studia\Semestr_7\Bazy_Danych_Przestrzennych\Laby\cw7\ras250_gb\ras250_gb\data\TM.tif" "D:\AGH-studia\Semestr_7\Bazy_Danych_Przestrzennych\Laby\cw7\ras250_gb\ras250_gb\data\TQ.tif" "D:\AGH-studia\Semestr_7\Bazy_Danych_Przestrzennych\Laby\cw7\ras250_gb\ras250_gb\data\TR.tif" "D:\AGH-studia\Semestr_7\Bazy_Danych_Przestrzennych\Laby\cw7\ras250_gb\ras250_gb\data\TV.tif""   # Source GeoTIFF File(s) or URL(s)
- SourceDataset_POSTGIS_3 = postgresql   # Connection
- SourceDataset_POSTGIS = postgresql   # Connection
- SourceDataset_POSTGIS_RASTER = postgresql   # Connection
- DestDataset_POSTGIS_RASTER_4 = postgresql   # Connection

Readers:
- SHAPEFILE_1: SHAPEFILE from $(SourceDataset_SHAPEFILE)
- GEOTIFF_1: GEOTIFF from $(SourceDataset_GEOTIFF)
- POSTGIS_1: POSTGIS from $(SourceDataset_POSTGIS) in LL-WGS84
- POSTGIS_2: POSTGIS from $(SourceDataset_POSTGIS_3)
- POSTGIS_RASTER_1: POSTGIS_RASTER from $(SourceDataset_POSTGIS_RASTER)

Writers:
- POSTGIS_RASTER_3: POSTGIS_RASTER to $(DestDataset_POSTGIS_RASTER_4)

scotland_and_wales_region (reader SHAPEFILE_1)
    attributes: NAME varchar(100), AREA_CODE varchar(3), DESCRIPTIO varchar(50), FILE_NAME varchar(100), NUMBER number(11,0), NUMBER0 number(11,0), POLYGON_ID number(11,0), UNIT_ID number(11,0), CODE varchar(9), HECTARES float, AREA float, TYPE_CODE varchar(2), DESCRIPT0 varchar(25), TYPE_COD0 varchar(3), DESCRIPT1 varchar(36)
    -> Tester
Tester
    BOOL_OP = OR
    TEST_CLAUSE = CASE_INSENSITIVE_TEST @Value(NAME) BEGINS_WITH South Wales
    TEST_MODE = TEST
    PASSED -> Aggregator
Aggregator
    ACCUM_ATTRS_NAME = Use Attributes From One Feature
    AGGREGATE_TYPE = Homogeneous Collection (If Possible)
    MODE = Geometry - Assemble One Level
    SEP = ,
    AGGREGATE -> Clipper [CLIPPER]
GEOTIFF (reader GEOTIFF_1)
    -> Clipper [CANDIDATE]
Clipper
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> RasterPaletteResolver
RasterPaletteResolver
    -> scotland_and_wales_region (writer POSTGIS_RASTER_3)
scotland_and_wales_region (writer POSTGIS_RASTER_3)
    attributes: name varchar(100), area_code varchar(3), descriptio varchar(50), file_name varchar(100), number int8, number0 int8, polygon_id int8, unit_id int8, code varchar(9), hectares float4, area float4, type_code varchar(2), descript0 varchar(25), type_cod0 varchar(3), descript1 varchar(36)
